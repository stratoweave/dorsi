module netinfra-inter {
  yang-version "1.1";
  namespace "http://example.com/netinfra-inter";
  prefix "netinfra-inter";
  description "Network Infrastructure intermediate";
  revision 2019-01-01 {
    description "test revision";
    reference "ref1";
  }
  import ietf-inet-types {
    prefix inet;
  }
  import stratoweave {
    prefix sw;
  }

  container netinfra {
    description "Network infrastructure";
    list router {
      key name;

      sw:transform dorsi.inter.Router;

      leaf name {
        type string;
      }
      leaf id {
        type uint32;
        description "router id";
        mandatory true;
      }
      leaf type {
        type string;
      }
      leaf role {
        type string;
      }
      leaf mock {
        type boolean;
        default false;
      }
      leaf approval-required {
        type boolean;
        default false;
      }
      container feature-flags {
        leaf runtime-schema-fetch {
          type boolean;
          default false;
        }
      }
      container base-config {
        leaf asn {
          type inet:as-number;
          mandatory true;
        }
        // Allocated to the router in the CFS layer
        leaf ipv4-address {
          type inet:ipv4-address;
          mandatory true;
        }
        // Allocated to the router in the CFS layer
        leaf ipv6-address {
          type inet:ipv6-address;
          mandatory true;
        }
      }
    }

    list backbone-link {
      key "left-router left-interface right-router right-interface";

      sw:transform dorsi.inter.BBLink;

      leaf left-router {
        type string;
      }
      leaf left-interface {
        type string;
      }
      leaf right-router {
        type string;
      }
      leaf right-interface {
        type string;
      }

      container state {
        config false;
        description
          "Combined oper-state of the two endpoints, lifted from the RFS
           backbone-interface entries: up only when both endpoints are up,
           down if either is down, unknown when either is unavailable.";
        leaf link-status {
          type enumeration {
            enum up;
            enum down;
            enum unknown;
          }
        }
      }
    }

    list ibgp-fullmesh {
      key "asn";
      leaf asn {
        type inet:as-number;
      }
      leaf authentication-key {
        type string;
        mandatory true;
      }

      sw:transform dorsi.inter.IbgpFullmesh;

      list router {
        key "name";
        leaf name {
          type string;
        }
        leaf ipv4-address {
          type inet:ipv4-address;
          mandatory true;
        }
      }
    }
  }
}
