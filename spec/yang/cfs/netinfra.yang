module netinfra {
  yang-version "1.1";
  namespace "http://example.com/netinfra";
  prefix "netinfra";
  description "Network Infrastructure";
  revision 2019-01-01 {
    description "test revision";
    reference "ref1";
  }
  import ietf-inet-types {
    prefix inet;
  }
  import stratoweave {
    prefix sw;
  }
  import ietf-yang-tmf-map {
    prefix tmf;
  }

  container netinfra {
    description "Network infrastructure";
    list router {
      description "Network Infrastructure Router";
      key name;

      sw:transform dorsi.cfs.Router;
      tmf:cfs-service "Router";

      leaf name {
        type string;
      }
      leaf id {
        type uint32;
        description "router id";
        mandatory true;
      }
      leaf type {
        type string;
        mandatory true;
      }
      leaf role {
        type string;
      }
      leaf asn {
        type inet:as-number;
        mandatory true;
      }
      leaf mock {
        type boolean;
        default false;
      }
      leaf approval-required {
        type boolean;
        default false;
      }
      container feature-flags {
        leaf runtime-schema-fetch {
          type boolean;
          default false;
        }
      }
    }

    list backbone-link {
      key "left-router left-interface right-router right-interface";

      sw:transform dorsi.cfs.BBLink;
      tmf:cfs-service "Backbone Link";

      leaf left-router {
        type string;
      }
      leaf left-interface {
        type string;
      }
      leaf right-router {
        type string;
      }
      leaf right-interface {
        type string;
      }

      container state {
        config false;
        description
          "Combined oper-state of the link, lifted from the underlying RFS
           backbone-interface entries: up only when both endpoints are up,
           down if either is down, unknown when either is unavailable.";
        leaf link-status {
          type enumeration {
            enum up;
            enum down;
            enum unknown;
          }
        }
      }
    }

    list ibgp-fullmesh {
      description
        "iBGP full-mesh between the listed routers. Every member peers with
         every other member, using the loopback addresses allocated by the
         router transform.";
      key asn;

      sw:transform dorsi.cfs.IbgpFullmesh;
      sw:link global {
        sw:path /netinfra:netinfra/netinfra:global-settings;
      }

      leaf asn {
        type inet:as-number;
      }
      leaf-list router {
        sw:link member;
        type leafref {
          path "/netinfra:netinfra/netinfra:router/netinfra:name";
        }
        description "Routers in the full-mesh.";
      }
    }

    container global-settings {
      sw:transform dorsi.cfs.GlobalSettings;
      description
        "Network-wide settings shared across all routers.";
      leaf ibgp-authentication-key {
        type string;
        mandatory true;
        description
          "Shared iBGP authentication key applied to every router's
           iBGP full-mesh neighbors.";
      }
    }
  }
}
